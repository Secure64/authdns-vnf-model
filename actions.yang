/*
 * File: actions.yang
 * Author: Ian Cohee
 *
 * This file models actions that are available on the 
 * Secure64 x86 DNS VNF server. At this time, the available 
 * actions are:
 *
 *     1. Start DNS
 *     2. Stop DNS
 *     3. Reconfig
 *     4. reload
 *       4.1 reload <zone name>
 *     5. Status
 * */

module actions {
    namespace "http://secure64.com/actions";
    prefix ac;
    
    import tailf-common {
        prefix tailf;
    }

    organization "Secure64 Software Corp.";
    contact "support@secure64.com";

    description
        "This module describes actions that may be requested of the VNF instance. These actions are:
            
            stop     -    Stop the DNS service.
            start    -    Start the DNS service.
            reconfig -    Reload ``nsd.conf'' and apply changes to TSIG key and configuration patterns,
                          and apply the changes to add and remove zones that are mentioned in the config.
                          Other changes are not applied, such as listening ip addres and port.
            reload   -    Reload zonefiles and reopen logilfe. Without argument reads changed zonefiles.
                          With argument reads the zonefile for the given zone and loads it.
            status   -    Display server status.";

    revision 2016-09-30 {
        description "Initial version.";
    }

    container actions {
        tailf:action start {
            tailf:actionpoint status-point;
            input {}
            output {
                leaf output {
                    type string;
                    mandatory true;
                }
            }
        }
        tailf:action stop {
            tailf:actionpoint status-point;
            input {}
            output { 
                leaf output {
                    type string;
                    mandatory true;
                }    
            }
        }
        tailf:action reconfig {
            tailf:actionpoint status-point;
            input {}
            output {
                leaf output {
                    type string;
                    mandatory true;
                }    
            }
        }
        tailf:action reload {
            tailf:actionpoint status-point;
            input {
                leaf zone {
                    type string;
                    mandatory false;
                }    
            }
            output {
                leaf output {
                    type string;
                    mandatory true;
                }    
            }
        }
        tailf:action status {
            tailf:actionpoint status-point;
            input {}
            output {
                leaf output {
                    type string; 
                    mandatory true;
                }    
            }
        }
    }
}
